module telemetrify-ext {
  yang-version 1.1;
  namespace "urn:example:telemetrify-ext";
  prefix tlme;

  import ietf-inet-types {
    prefix inet;
  }

  import ietf-yang-types {
    prefix yang;
  }

  import telemetrify {
    prefix tlm;
  }

  description
      "Example Telemetrify extentension.";

  revision 2024-05-27 {
    description
      "Initial revision.";
  }

  augment "/tlm:telemetrify/tlm:transform/tlm:type/tlm:transform-type" {
    // TODO
    container example {
      presence true;
    }
  }
}
