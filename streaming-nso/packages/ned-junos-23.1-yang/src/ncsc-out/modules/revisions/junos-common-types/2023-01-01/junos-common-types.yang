module junos-common-types {
  // Generated by yanger -t ncs
  tailf:mount-id "ned-junos-23.1-yang-nc-1.0:ned-junos-23.1-yang-nc-1.0";
  tailf:ncs-device-type "netconf";

  namespace "http://yang.juniper.net/junos/common/types";
  prefix jt;

  import tailf-common {
    prefix tailf;
  }
  import tailf-ncs {
    prefix ncs;
  }

  organization
    "Juniper Networks, Inc.";
  contact
    "yang-support@juniper.net";
  description
    "This module contains definitions for Junos YANG types.";

  revision 2023-01-01 {
    description
      "Junos: 23.1R1.8";
  }

  typedef ncs_compliance_template_daemon {
    type string;
  }

  typedef ncs_compliance_template_filename {
    type string;
  }

  typedef ncs_compliance_template_client-filename {
    type string;
  }

  typedef ncs_compliance_template_hostname {
    type string;
  }

  typedef ncs_compliance_template_ipaddr {
    type string;
  }

  typedef ncs_compliance_template_sysid {
    type string;
  }

  typedef ncs_compliance_template_interface-device {
    type string;
  }

  typedef ncs_compliance_template_ddl-bits {
    type string;
  }

  typedef ncs_compliance_template_isoaddr {
    type string;
  }

  typedef ncs_compliance_template_ipprefix {
    type string;
  }

  typedef ncs_compliance_template_ipprefix-mandatory {
    type string;
  }

  typedef ncs_compliance_template_interface-unit {
    type string;
  }

  typedef ncs_compliance_template_ipaddr-or-interface {
    type string;
  }

  typedef ncs_compliance_template_areaid {
    type string;
  }

  typedef ncs_compliance_template_interface-name {
    type string;
  }

  typedef ncs_compliance_template_community {
    type string;
  }

  typedef ncs_compliance_template_interface-wildcard {
    type string;
  }

  typedef ncs_compliance_template_unreadable {
    type string;
  }

  typedef ncs_compliance_template_ipprefix-optional {
    type string;
  }

  typedef ncs_compliance_template_policy-algebra {
    type string;
  }

  typedef ncs_compliance_template_regular-expression {
    type string;
  }

  typedef ncs_compliance_template_group-glob {
    type string;
  }

  typedef ncs_compliance_template_atm-vci {
    type string;
  }

  typedef ncs_compliance_template_ipprefix-only {
    type string;
  }

  typedef ncs_compliance_template_ipv4addr {
    type string;
  }

  typedef ncs_compliance_template_ipv4prefix {
    type string;
  }

  typedef ncs_compliance_template_ipv4prefix-mandatory {
    type string;
  }

  typedef ncs_compliance_template_ipv4addr-or-interface {
    type string;
  }

  typedef ncs_compliance_template_ipv4prefix-optional {
    type string;
  }

  typedef ncs_compliance_template_ipv4prefix-only {
    type string;
  }

  typedef ncs_compliance_template_ipv6addr {
    type string;
  }

  typedef ncs_compliance_template_ipv6prefix {
    type string;
  }

  typedef ncs_compliance_template_ipv6prefix-mandatory {
    type string;
  }

  typedef ncs_compliance_template_ipv6addr-or-interface {
    type string;
  }

  typedef ncs_compliance_template_ipv6prefix-optional {
    type string;
  }

  typedef ncs_compliance_template_ipv6prefix-only {
    type string;
  }

  typedef ncs_compliance_template_interface-device-wildcard {
    type string;
  }

  typedef ncs_compliance_template_time {
    type string;
  }

  typedef ncs_compliance_template_mac-addr {
    type string;
  }

  typedef ncs_compliance_template_mac-addr-prefix {
    type string;
  }

  typedef ncs_compliance_template_mac-unicast {
    type string;
  }

  typedef ncs_compliance_template_mac-unicast-prefix {
    type string;
  }

  typedef ncs_compliance_template_mac-multicast {
    type string;
  }

  typedef ncs_compliance_template_mac-multicast-prefix {
    type string;
  }

  typedef ncs_compliance_template_mpls-label {
    type string;
  }

  typedef ncs_compliance_template_unsigned-float {
    type string;
  }

  typedef ncs_compliance_template_isoprefix {
    type string;
  }

  typedef ncs_compliance_template_isosysid {
    type string;
  }

  typedef ncs_compliance_template_string-huge {
    type string;
  }

  typedef ncs_compliance_template_variable {
    type string;
  }

  typedef ncs_compliance_template_glob-variable {
    type string;
  }

  typedef ncs_compliance_template_vlan-range {
    type string;
  }

  typedef ncs_compliance_template_interface-range-wild {
    type string;
  }

  typedef ncs_compliance_template_fc-addr {
    type string;
  }

  typedef ncs_compliance_template_wwn {
    type string;
  }

  typedef ncs_compliance_template_logfilename {
    type string;
  }

  typedef ncs_compliance_template_range {
    type string;
  }

  typedef ncs_compliance_template_esi {
    type string;
  }

  typedef ncs_compliance_template_time-of-day {
    type string;
  }

  typedef ncs_compliance_template_date {
    type string;
  }

  typedef ncs_compliance_template_ipaddr-scoped {
    type string;
  }

  typedef ncs_template_daemon {
    type string;
  }

  typedef ncs_template_filename {
    type string;
  }

  typedef ncs_template_client-filename {
    type string;
  }

  typedef ncs_template_hostname {
    type string;
  }

  typedef ncs_template_ipaddr {
    type string;
  }

  typedef ncs_template_sysid {
    type string;
  }

  typedef ncs_template_interface-device {
    type string;
  }

  typedef ncs_template_ddl-bits {
    type string;
  }

  typedef ncs_template_isoaddr {
    type string;
  }

  typedef ncs_template_ipprefix {
    type string;
  }

  typedef ncs_template_ipprefix-mandatory {
    type string;
  }

  typedef ncs_template_interface-unit {
    type string;
  }

  typedef ncs_template_ipaddr-or-interface {
    type string;
  }

  typedef ncs_template_areaid {
    type string;
  }

  typedef ncs_template_interface-name {
    type string;
  }

  typedef ncs_template_community {
    type string;
  }

  typedef ncs_template_interface-wildcard {
    type string;
  }

  typedef ncs_template_unreadable {
    type string;
  }

  typedef ncs_template_ipprefix-optional {
    type string;
  }

  typedef ncs_template_policy-algebra {
    type string;
  }

  typedef ncs_template_regular-expression {
    type string;
  }

  typedef ncs_template_group-glob {
    type string;
  }

  typedef ncs_template_atm-vci {
    type string;
  }

  typedef ncs_template_ipprefix-only {
    type string;
  }

  typedef ncs_template_ipv4addr {
    type string;
  }

  typedef ncs_template_ipv4prefix {
    type string;
  }

  typedef ncs_template_ipv4prefix-mandatory {
    type string;
  }

  typedef ncs_template_ipv4addr-or-interface {
    type string;
  }

  typedef ncs_template_ipv4prefix-optional {
    type string;
  }

  typedef ncs_template_ipv4prefix-only {
    type string;
  }

  typedef ncs_template_ipv6addr {
    type string;
  }

  typedef ncs_template_ipv6prefix {
    type string;
  }

  typedef ncs_template_ipv6prefix-mandatory {
    type string;
  }

  typedef ncs_template_ipv6addr-or-interface {
    type string;
  }

  typedef ncs_template_ipv6prefix-optional {
    type string;
  }

  typedef ncs_template_ipv6prefix-only {
    type string;
  }

  typedef ncs_template_interface-device-wildcard {
    type string;
  }

  typedef ncs_template_time {
    type string;
  }

  typedef ncs_template_mac-addr {
    type string;
  }

  typedef ncs_template_mac-addr-prefix {
    type string;
  }

  typedef ncs_template_mac-unicast {
    type string;
  }

  typedef ncs_template_mac-unicast-prefix {
    type string;
  }

  typedef ncs_template_mac-multicast {
    type string;
  }

  typedef ncs_template_mac-multicast-prefix {
    type string;
  }

  typedef ncs_template_mpls-label {
    type string;
  }

  typedef ncs_template_unsigned-float {
    type string;
  }

  typedef ncs_template_isoprefix {
    type string;
  }

  typedef ncs_template_isosysid {
    type string;
  }

  typedef ncs_template_string-huge {
    type string;
  }

  typedef ncs_template_variable {
    type string;
  }

  typedef ncs_template_glob-variable {
    type string;
  }

  typedef ncs_template_vlan-range {
    type string;
  }

  typedef ncs_template_interface-range-wild {
    type string;
  }

  typedef ncs_template_fc-addr {
    type string;
  }

  typedef ncs_template_wwn {
    type string;
  }

  typedef ncs_template_logfilename {
    type string;
  }

  typedef ncs_template_range {
    type string;
  }

  typedef ncs_template_esi {
    type string;
  }

  typedef ncs_template_time-of-day {
    type string;
  }

  typedef ncs_template_date {
    type string;
  }

  typedef ncs_template_ipaddr-scoped {
    type string;
  }

  typedef ncs_rpc_notif_daemon {
    type string;
  }

  typedef ncs_rpc_notif_filename {
    type string;
  }

  typedef ncs_rpc_notif_client-filename {
    type string;
  }

  typedef ncs_rpc_notif_hostname {
    type string;
  }

  typedef ncs_rpc_notif_ipaddr {
    type string;
  }

  typedef ncs_rpc_notif_sysid {
    type string;
  }

  typedef ncs_rpc_notif_interface-device {
    type string;
  }

  typedef ncs_rpc_notif_ddl-bits {
    type string;
  }

  typedef ncs_rpc_notif_isoaddr {
    type string;
  }

  typedef ncs_rpc_notif_ipprefix {
    type string;
  }

  typedef ncs_rpc_notif_ipprefix-mandatory {
    type string;
  }

  typedef ncs_rpc_notif_interface-unit {
    type string;
  }

  typedef ncs_rpc_notif_ipaddr-or-interface {
    type string;
  }

  typedef ncs_rpc_notif_areaid {
    type string;
  }

  typedef ncs_rpc_notif_interface-name {
    type string;
  }

  typedef ncs_rpc_notif_community {
    type string;
  }

  typedef ncs_rpc_notif_interface-wildcard {
    type string;
  }

  typedef ncs_rpc_notif_unreadable {
    type string;
  }

  typedef ncs_rpc_notif_ipprefix-optional {
    type string;
  }

  typedef ncs_rpc_notif_policy-algebra {
    type string;
  }

  typedef ncs_rpc_notif_regular-expression {
    type string;
  }

  typedef ncs_rpc_notif_group-glob {
    type string;
  }

  typedef ncs_rpc_notif_atm-vci {
    type string;
  }

  typedef ncs_rpc_notif_ipprefix-only {
    type string;
  }

  typedef ncs_rpc_notif_ipv4addr {
    type string;
  }

  typedef ncs_rpc_notif_ipv4prefix {
    type string;
  }

  typedef ncs_rpc_notif_ipv4prefix-mandatory {
    type string;
  }

  typedef ncs_rpc_notif_ipv4addr-or-interface {
    type string;
  }

  typedef ncs_rpc_notif_ipv4prefix-optional {
    type string;
  }

  typedef ncs_rpc_notif_ipv4prefix-only {
    type string;
  }

  typedef ncs_rpc_notif_ipv6addr {
    type string;
  }

  typedef ncs_rpc_notif_ipv6prefix {
    type string;
  }

  typedef ncs_rpc_notif_ipv6prefix-mandatory {
    type string;
  }

  typedef ncs_rpc_notif_ipv6addr-or-interface {
    type string;
  }

  typedef ncs_rpc_notif_ipv6prefix-optional {
    type string;
  }

  typedef ncs_rpc_notif_ipv6prefix-only {
    type string;
  }

  typedef ncs_rpc_notif_interface-device-wildcard {
    type string;
  }

  typedef ncs_rpc_notif_time {
    type string;
  }

  typedef ncs_rpc_notif_mac-addr {
    type string;
  }

  typedef ncs_rpc_notif_mac-addr-prefix {
    type string;
  }

  typedef ncs_rpc_notif_mac-unicast {
    type string;
  }

  typedef ncs_rpc_notif_mac-unicast-prefix {
    type string;
  }

  typedef ncs_rpc_notif_mac-multicast {
    type string;
  }

  typedef ncs_rpc_notif_mac-multicast-prefix {
    type string;
  }

  typedef ncs_rpc_notif_mpls-label {
    type string;
  }

  typedef ncs_rpc_notif_unsigned-float {
    type string;
  }

  typedef ncs_rpc_notif_isoprefix {
    type string;
  }

  typedef ncs_rpc_notif_isosysid {
    type string;
  }

  typedef ncs_rpc_notif_string-huge {
    type string;
  }

  typedef ncs_rpc_notif_variable {
    type string;
  }

  typedef ncs_rpc_notif_glob-variable {
    type string;
  }

  typedef ncs_rpc_notif_vlan-range {
    type string;
  }

  typedef ncs_rpc_notif_interface-range-wild {
    type string;
  }

  typedef ncs_rpc_notif_fc-addr {
    type string;
  }

  typedef ncs_rpc_notif_wwn {
    type string;
  }

  typedef ncs_rpc_notif_logfilename {
    type string;
  }

  typedef ncs_rpc_notif_range {
    type string;
  }

  typedef ncs_rpc_notif_esi {
    type string;
  }

  typedef ncs_rpc_notif_time-of-day {
    type string;
  }

  typedef ncs_rpc_notif_date {
    type string;
  }

  typedef ncs_rpc_notif_ipaddr-scoped {
    type string;
  }

  typedef live_ncs_daemon {
    type string;
  }

  typedef live_ncs_filename {
    type string;
  }

  typedef live_ncs_client-filename {
    type string;
  }

  typedef live_ncs_hostname {
    type string;
  }

  typedef live_ncs_ipaddr {
    type string;
  }

  typedef live_ncs_sysid {
    type string;
  }

  typedef live_ncs_interface-device {
    type string;
  }

  typedef live_ncs_ddl-bits {
    type string;
  }

  typedef live_ncs_isoaddr {
    type string;
  }

  typedef live_ncs_ipprefix {
    type string;
  }

  typedef live_ncs_ipprefix-mandatory {
    type string;
  }

  typedef live_ncs_interface-unit {
    type string;
  }

  typedef live_ncs_ipaddr-or-interface {
    type string;
  }

  typedef live_ncs_areaid {
    type string;
  }

  typedef live_ncs_interface-name {
    type string;
  }

  typedef live_ncs_community {
    type string;
  }

  typedef live_ncs_interface-wildcard {
    type string;
  }

  typedef live_ncs_unreadable {
    type string;
  }

  typedef live_ncs_ipprefix-optional {
    type string;
  }

  typedef live_ncs_policy-algebra {
    type string;
  }

  typedef live_ncs_regular-expression {
    type string;
  }

  typedef live_ncs_group-glob {
    type string;
  }

  typedef live_ncs_atm-vci {
    type string;
  }

  typedef live_ncs_ipprefix-only {
    type string;
  }

  typedef live_ncs_ipv4addr {
    type string;
  }

  typedef live_ncs_ipv4prefix {
    type string;
  }

  typedef live_ncs_ipv4prefix-mandatory {
    type string;
  }

  typedef live_ncs_ipv4addr-or-interface {
    type string;
  }

  typedef live_ncs_ipv4prefix-optional {
    type string;
  }

  typedef live_ncs_ipv4prefix-only {
    type string;
  }

  typedef live_ncs_ipv6addr {
    type string;
  }

  typedef live_ncs_ipv6prefix {
    type string;
  }

  typedef live_ncs_ipv6prefix-mandatory {
    type string;
  }

  typedef live_ncs_ipv6addr-or-interface {
    type string;
  }

  typedef live_ncs_ipv6prefix-optional {
    type string;
  }

  typedef live_ncs_ipv6prefix-only {
    type string;
  }

  typedef live_ncs_interface-device-wildcard {
    type string;
  }

  typedef live_ncs_time {
    type string;
  }

  typedef live_ncs_mac-addr {
    type string;
  }

  typedef live_ncs_mac-addr-prefix {
    type string;
  }

  typedef live_ncs_mac-unicast {
    type string;
  }

  typedef live_ncs_mac-unicast-prefix {
    type string;
  }

  typedef live_ncs_mac-multicast {
    type string;
  }

  typedef live_ncs_mac-multicast-prefix {
    type string;
  }

  typedef live_ncs_mpls-label {
    type string;
  }

  typedef live_ncs_unsigned-float {
    type string;
  }

  typedef live_ncs_isoprefix {
    type string;
  }

  typedef live_ncs_isosysid {
    type string;
  }

  typedef live_ncs_string-huge {
    type string;
  }

  typedef live_ncs_variable {
    type string;
  }

  typedef live_ncs_glob-variable {
    type string;
  }

  typedef live_ncs_vlan-range {
    type string;
  }

  typedef live_ncs_interface-range-wild {
    type string;
  }

  typedef live_ncs_fc-addr {
    type string;
  }

  typedef live_ncs_wwn {
    type string;
  }

  typedef live_ncs_logfilename {
    type string;
  }

  typedef live_ncs_range {
    type string;
  }

  typedef live_ncs_esi {
    type string;
  }

  typedef live_ncs_time-of-day {
    type string;
  }

  typedef live_ncs_date {
    type string;
  }

  typedef live_ncs_ipaddr-scoped {
    type string;
  }

  typedef daemon {
    type string;
  }

  typedef filename {
    type string;
  }

  typedef client-filename {
    type string;
  }

  typedef hostname {
    type string;
  }

  typedef ipaddr {
    type string;
  }

  typedef sysid {
    type string;
  }

  typedef interface-device {
    type string;
  }

  typedef ddl-bits {
    type string;
  }

  typedef isoaddr {
    type string;
  }

  typedef ipprefix {
    type string;
  }

  typedef ipprefix-mandatory {
    type string;
  }

  typedef interface-unit {
    type string;
  }

  typedef ipaddr-or-interface {
    type string;
  }

  typedef areaid {
    type string;
  }

  typedef interface-name {
    type string;
  }

  typedef community {
    type string;
  }

  typedef interface-wildcard {
    type string;
  }

  typedef unreadable {
    type string;
  }

  typedef ipprefix-optional {
    type string;
  }

  typedef policy-algebra {
    type string;
  }

  typedef regular-expression {
    type string;
  }

  typedef group-glob {
    type string;
  }

  typedef atm-vci {
    type string;
  }

  typedef ipprefix-only {
    type string;
  }

  typedef ipv4addr {
    type string;
  }

  typedef ipv4prefix {
    type string;
  }

  typedef ipv4prefix-mandatory {
    type string;
  }

  typedef ipv4addr-or-interface {
    type string;
  }

  typedef ipv4prefix-optional {
    type string;
  }

  typedef ipv4prefix-only {
    type string;
  }

  typedef ipv6addr {
    type string;
  }

  typedef ipv6prefix {
    type string;
  }

  typedef ipv6prefix-mandatory {
    type string;
  }

  typedef ipv6addr-or-interface {
    type string;
  }

  typedef ipv6prefix-optional {
    type string;
  }

  typedef ipv6prefix-only {
    type string;
  }

  typedef interface-device-wildcard {
    type string;
  }

  typedef time {
    type string;
  }

  typedef mac-addr {
    type string;
  }

  typedef mac-addr-prefix {
    type string;
  }

  typedef mac-unicast {
    type string;
  }

  typedef mac-unicast-prefix {
    type string;
  }

  typedef mac-multicast {
    type string;
  }

  typedef mac-multicast-prefix {
    type string;
  }

  typedef mpls-label {
    type string;
  }

  typedef unsigned-float {
    type string;
  }

  typedef isoprefix {
    type string;
  }

  typedef isosysid {
    type string;
  }

  typedef string-huge {
    type string;
  }

  typedef variable {
    type string;
  }

  typedef glob-variable {
    type string;
  }

  typedef vlan-range {
    type string;
  }

  typedef interface-range-wild {
    type string;
  }

  typedef fc-addr {
    type string;
  }

  typedef wwn {
    type string;
  }

  typedef logfilename {
    type string;
  }

  typedef range {
    type string;
  }

  typedef esi {
    type string;
  }

  typedef time-of-day {
    type string;
  }

  typedef date {
    type string;
  }

  typedef ipaddr-scoped {
    type string;
  }
}
