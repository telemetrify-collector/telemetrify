module ned-junos-23.1-yang-nc {
  yang-version 1.1;
  namespace "http://tail-f.com/ns/ned-id/ned-junos-23.1-yang-nc";
  prefix ned-junos-23.1-yang-nc;

  import tailf-common {
    prefix tailf;
  }

  import tailf-ncs-ned {
    prefix ned;
  }

  identity ned-junos-23.1-yang-nc {
    tailf:abstract;
    base ned:netconf-ned-id;
  }
}
