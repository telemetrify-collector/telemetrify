module telemetrify-transform {
  yang-version 1.1;
  namespace "urn:telekom:abs:telemetrify-transform";
  prefix tlmt;

  import ietf-inet-types {
    prefix inet;
  }

  import ietf-yang-types {
    prefix yang;
  }

  import tailf-common {
    prefix tailf;
  }

  import tailf-ncs {
    prefix ncs;
  }

  import tailf-ncs-ned {
    prefix ned;
  }

  import telemetrify {
    prefix tlm;
  }

  description
      "Telemetry streaming implemented in Acton";

  revision 2024-04-10 {
    description
      "Initial revision.";
  }

  augment "/tlm:telemetrify/tlm:transform/tlm:type/tlm:transform-type" {
    container vmanage {
      presence true;
    }

    container cat8k-ip-sla {
      presence true;
    }
  }
}
