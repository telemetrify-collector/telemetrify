module telemetrify-ext {
  yang-version 1.1;
  namespace "urn:example:telemetrify-ext";
  prefix tlme;

  import ietf-inet-types {
    prefix inet;
  }

  import ietf-yang-types {
    prefix yang;
  }

  import tailf-ncs-alarms {
    prefix al;
  }

  import telemetrify {
    prefix tlm;
  }

  description
      "Example Telemetrify extentension.";

  revision 2024-05-27 {
    description
      "Initial revision.";
  }

  identity backbone-alarm {
    base al:alarm-type;
  }

  identity backbone-interface-down {
    base al:alarm-type;
    base backbone-alarm;
  }

  augment "/tlm:telemetrify/tlm:transform/tlm:type/tlm:transform-type" {
    container vmanage {
      presence true;
    }

    container cat8k-ip-sla {
      presence true;
    }

    container backbone-interface-alarm-junos {
      presence true;

      leaf device {
        mandatory true;
        // type leafref {
        //   path "/ncs:devices/ncs:device/ncs:name";
        // }
        type string;
      }

      leaf interface-name {
        mandatory true;
        type string;
      }

      leaf service-instance {
        mandatory true;
        description "As alarm managed-object";
        // type managed-object-t;
        type string;
      }
    }
  }
}
